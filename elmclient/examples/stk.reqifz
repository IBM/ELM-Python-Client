# IBM Engineering Requirements Mon Mar 14 04:17:37 PDT 2022

# Specification: AMR Stakeholder Requirements Specification
- ReqIF.Name: AMR Stakeholder Requirements Specification
- Artifact Format: Module

## 4448: Introduction (Heading)
- Artifact Format: Text

### 4594: ANSI 1252 Latin 1 for CSV Export (Information)
- Artifact Format: Text

### 4632: newest (Information)
- Artifact Format: Text

### 4429: Purpose of the Document (Heading)
- Artifact Format: Text

#### 4458: The Stakeholder requirements describe the user needs for a water meter reading system (AMR) including the meter, the method of collecting data from the device, and the means by which the customers will be billed for usage. (Information)
- Artifact Format: Text

#### 4516: The AMR product is intended to allow water providers to lower their cost of operation by more accurately measureing consumption and more quickly gather data. (Information)
- Artifact Format: Text

### 4354: Intended Use (Heading)
- Artifact Format: Text

#### 4465: The AMR is intended for gathering and reporting of water consumtion data to facilitate measurement of residential and business customers. (Information)
- Artifact Format: Text

#### 4291: Upaload Usage Data Locally (Diagrams and sketches)
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- Artifact Format: Diagram
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
### 4285: Definitions Acronyms, and Abbreviations (Heading)
- Artifact Format: Text

#### 4367: Term (Information)
| Term | Definition |
| --- | --- |
| AMR | Automatic Meter Reader |
| MMIU | Multi-channel Meter Interface Unit |
| CTRL | Central Control Center |
- Artifact Format: Text

## 4579: General Description (Heading)
- Artifact Format: Text

### 4461: Scope of the System (Heading)
- Artifact Format: Text

#### 4359: The system, when deployed, will initially include water service for residential, commercial and industrial customers inside a 72 square mile area (~79,000 meter connections). (Stakeholder Requirement)
- Artifact Format: Text
- Status: In Process

#### 4549 (Stakeholder Requirement)
The desired solution leverages the existing infrastructure of meters, but may require enhancements to support a more flexible means of determining water consumption. The goal is to best provide services and read meters in an electronically automated and cost effective manner. It is expected that the system(s) will be made up of sufficient equipment such that if a failure of any major system component or part thereof does occur, it will not interrupt the flow of meter reading information to customer revenue systems.
- Status: Approved
- Artifact Format: Text

#### 4356: The AMR system shall have an operational life of no less than five years. (Stakeholder Requirement)
- Verification Method: Not Set
- Accepted: false
- Artifact Format: Text
- Verifiability: false

### 4541: Product Perspective (Heading)
- Artifact Format: Text

#### 4564: Configuration (Heading)
- Artifact Format: Text

#### 4556: Performance (Heading)
- Artifact Format: Text

##### 4492: The systems shall meet the following objectives: (Stakeholder Requirement)
- Artifact Format: Text
- Status: Approved

##### 4294: Meter reading in the most cost effective manner possible (Stakeholder Requirement)
- Meter reading in the most cost effective manner possible
- Artifact Format: Text
- Status: In Process

##### 4417: A system goal of 100% accurate, 100% reliable, 100% of the time (Stakeholder Requirement)
- A system goal of 100% accurate, 100% reliable, 100% of the time
- Artifact Format: Text
- Status: Rejected

##### 4558: Ability to perform advanced data analysis of incremental meter readings (Stakeholder Requirement)
- Ability to perform advanced data analysis of incremental meter readings
- Artifact Format: Text

##### 4561: Maximization of existing investments in meter reading technology (Stakeholder Requirement)
- Maximization of existing investments in meter reading technology
- Status: Postponed
- Artifact Format: Text

##### 4554: Support conservation monitoring and enforcement (Stakeholder Requirement)
- Support conservation monitoring and enforcement
- Status: Obsolete
- Artifact Format: Text

##### 4436: Provide accurate meter readings (Stakeholder Requirement)
- Provide accurate meter readings
- Artifact Format: Text
- Status: Approved

### 4455: User Characteristics (Heading)
- Artifact Format: Text

#### 4435: Usability (Heading)
- Artifact Format: Text

##### 4493: A trained user shall be able to use all aspects of the system within no more than one minutes of system startup. (Stakeholder Requirement)
- Artifact Format: Text
- Status: In Process

### 4422: Reliability and Service (Heading)
- Artifact Format: Text

#### 4501: The AMR system shall have an operational life of no less than five years. (Stakeholder Requirement)
- Artifact Format: Text
- Status: Approved

### 4398: Operational Environment (Heading)
- Artifact Format: Text

#### 4512: The AMR system shall be able to operate in the market environments for which it is targeted and approved. (Stakeholder Requirement)
- Artifact Format: Text
- Status: Approved

#### 4525: Any portable equipment shall have an Ingress Protection Rating of IP66 or better in accordance with Standard IEC 60529. (Stakeholder Requirement)
- Artifact Format: Text
- Verification Method: Not Set
- Accepted: false
- Verifiability: false

#### 4415: All portable equipment should survive multiple 6 ft./1.8 m drops on to concrete, across the operating temperature range in accordance with Standard MIL-STD 810G. (Stakeholder Requirement)
- Artifact Format: Text

### 4433: Regulatory (Heading)
- Artifact Format: Text

#### 4396: The AMR system shall be approved for sale in the following markets: (Stakeholder Requirement)
- Artifact Format: Text

#### 4364: Brazil (Stakeholder Requirement)
- Brazil
- Canada
- China
- European Union
- Japan
- United States of America
- Artifact Format: Text

#### 4487: All portable equipment shall have Hazardous location certifications UL Class I, II, III Division II, A, B, C, D, F, G. (Stakeholder Requirement)
- Artifact Format: Text

#### 4401: The AMR system functions, reports, and data on the control computer shall be securely accessible by properly authorized persons from other workstations on the City’s network. (Stakeholder Requirement)
- Verification Method: Not Set
- Artifact Format: Text
- Verifiability: false
- Accepted: false

### 4625: Assumptions and Dependencies (Heading)
- Artifact Format: Text

## 4405: Specific Description (Heading)
- Artifact Format: Text

### 4350: Description (Heading)
- Artifact Format: Text

#### 4508 (Stakeholder Requirement)
In handheld AMR, a meter reader carries a handheld computer with the ability to collect meter readings from an AMR capable meter. This is sometimes referred to as "walk-by" meter reading since the meter reader walks by the locations where meters are installed as they go through their meter reading route. Handheld computers may also be used to manually enter readings without the use of AMR technology as an alternate but this will not support comprehensive data which can be accurately read using the meter reading electronically.
- Artifact Format: Text
- Status: Approved

### 4381: Handheld device (Heading)
- Artifact Format: Text

#### 4332: <Picture> (Stakeholder Requirement)
- Artifact Format: Text

#### 4276: Image 5 (Information)
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- Artifact Format: File
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
#### 4593: The handheld device shall allow for the meter reader to collect and store information from the meter. (Stakeholder Requirement)
- Status: Approved
- Artifact Format: Text

#### 4423: The handheld device shall have a human readable display for information collected from the meter. (Stakeholder Requirement)
- Artifact Format: Text
- Status: Approved

#### 4535 (Stakeholder Requirement)
The handheld device shall allow for upload of all information collected on handheld computers during meter rounds, so that data can be compiled. Data shall be retrievable to business office computers in a manner that will interface with the existing billing system.
- Status: Approved
- Artifact Format: Text

#### 4341: The handheld device shall allow the meter reader to access account information for a given address or meter. (Stakeholder Requirement)
- Status: Approved
- Artifact Format: Text

#### 4322: The handheld meter reading device shall allow for programming of a defined route, advancing to the next meter on the route as the meter reader moves through the route. (Stakeholder Requirement)
- Artifact Format: Text
- Status: Approved

#### 4580: The handheld device shall provide for the means for the meter reader to manually enter a meter reading or information about a meter reading such as (Stakeholder Requirement)
- Status: Approved
- Artifact Format: Text

#### 4333: meter irregularities; (Stakeholder Requirement)
- meter irregularities;
- Artifact Format: Text
- Status: Rejected

#### 4298: damage equipment (such as broken seals); (Stakeholder Requirement)
- damage equipment (such as broken seals);
- Verification Method: Not Set
- Status: Postponed
- Verifiability: false
- Artifact Format: Text
- Accepted: false

#### 4478: impediments to meter access, including dogs; (Stakeholder Requirement)
- impediments to meter access, including dogs;
- Artifact Format: Text
- Accepted: false
- Verification Method: Not Set
- Status: Obsolete
- Verifiability: false

#### 4317: consumption appears to be abnormal and / or record possible reasons for fluctuations. (Stakeholder Requirement)
- consumption appears to be abnormal and / or record possible reasons for fluctuations.
- Verifiability: false
- Verification Method: Not Set
- Accepted: false
- Status: Approved
- Artifact Format: Text

#### 4372: Update client address and meter location information. (Stakeholder Requirement)
- Update client address and meter location information.
- Verifiability: false
- Verification Method: Not Set
- Artifact Format: Text
- Status: Approved
- Accepted: false

#### 4311: The handheld device shall have a screen that displays the number of accounts that have been read and unread along with the total number of accounts, date/time, and the id of the handheld reading device. (Stakeholder Requirement)
- Artifact Format: Text
- Status: Approved

#### 4399: The handheld device shall have a mechanism to recharge the unit. (Stakeholder Requirement)
- Artifact Format: Text
- Status: Approved

#### 4306: The handheld device shall be capable of displaying diagnostic information, including suspected water leaks. (Stakeholder Requirement)
- Artifact Format: Text
- Status: In Process

#### 4438: The handheld device shall record leakage data on the central office data store. (Stakeholder Requirement)
- Artifact Format: Text
- Status: In Process

#### 4450: Any portable equipment shall be yellow. (Stakeholder Requirement)
- Artifact Format: Text

#### 4320: All external fixings for portable equipment shall be hexalobular internal driving feature T25 or T30 bolts in accordance with Standard ISO 10664 to improve serviceability. (Stakeholder Requirement)
- Artifact Format: Text

#### 4387: All portable equipment shall have a ruggedness of IK06 or better in accordance with Standard IEC 62262:2002. (Stakeholder Requirement)
- Artifact Format: Text

#### 4318: All portable equipment shall use standard rubber casing to Internal document 630-520-4587. (Stakeholder Requirement)
- Artifact Format: Text

#### 4413: Any exposed ports on portable equipment will be protected to IP67 or better in accordance with Standard IEC 60529. (Stakeholder Requirement)
- Artifact Format: Text

### 4410: Meter Interface Unit (Heading)
- Artifact Format: Text

#### 4406: <Picture> (Stakeholder Requirement)
- Artifact Format: Text

#### 4273: Image 4 (Information)
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- Artifact Format: File
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
#### 4577: The meter interface unit shall allow for at least one, but preferably several, mechanisms for data collection. (Stakeholder Requirement)
- Artifact Format: Text
- Status: Approved

#### 4480: The meter interface unit shall support all functions (data reading, time-triggered operation, and management) of the AMR system. (Stakeholder Requirement)
- Status: Approved
- Artifact Format: Text

#### 4289: The meter interface unit shall be compatible with the existing meter models in use for the area covered by this project. (Stakeholder Requirement)
- Artifact Format: Text
- Status: Rejected

#### 4589: The meter interface unit shall be compatible with MMIU. (Stakeholder Requirement)
- Artifact Format: Text
- Status: Approved

#### 4297: The meter interface unit shall be powered by a replaceable long lasting battery. (Stakeholder Requirement)
- Artifact Format: Text
- Status: Approved

#### 4329: The meter interface unit shall be able to collect meter data at regular intervals and store that data for up to one year. (Stakeholder Requirement)
- Artifact Format: Text
- Status: Approved

#### 4370: The meter interface unit shall store data for a defined period while powered off. (Stakeholder Requirement)
- Artifact Format: Text
- Status: Approved

#### 4362: The meter interface unit shall allow a mechanism to accept / retrieve software / firmware / system updates. (Stakeholder Requirement)
- Artifact Format: Text
- Status: In Process

#### 4379: The meter interface shall detect water leaks and record leak status with the account data. (Stakeholder Requirement)
- Status: Approved
- Artifact Format: Text

#### 4597: The meter interface shall log leakage data on the central office data store. (Stakeholder Requirement)
- Status: Approved
- Artifact Format: Text

### 4407: Fixed Network Automated Meter Reading System (Heading)
- Artifact Format: Text

#### 4328: <Picture> (Stakeholder Requirement)
- Artifact Format: Text

#### 4272: Image 3 (Information)
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- Artifact Format: File
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
#### 4288: The system shall be able to transmit and receive Meter data to the central office system without human intervention. (Stakeholder Requirement)
- Artifact Format: Text
- Status: Approved

#### 4611: Control Computer and Related Hardware (Heading)
- Artifact Format: Text

##### 4358: The processing servers/computers in the system shall run in a network configuration. (Stakeholder Requirement)
- Artifact Format: Text
- Status: Approved

##### 4394: The server shall communicate with the existing billing software. (Stakeholder Requirement)
- Artifact Format: Text
- Status: Approved

##### 4569: The AMR System control computer must operate on the most recent Windows platform currently available. (Stakeholder Requirement)
- Artifact Format: Text
- Status: In Process

##### 4369: The control computer must be capable of residing as a node on the City’s existing network. (Stakeholder Requirement)
- Artifact Format: Text
- Status: Approved

##### 4631: The Fixed Network Application software and data collection software must operate on a central server. (Stakeholder Requirement)
- Artifact Format: Text
- Status: Approved

##### 4345: The control computer shall be capable of operating in a normal office environment. (Stakeholder Requirement)
- Status: Approved
- Artifact Format: Text

##### 4500: The system software and functions shall be quickly and easily movable to another computer or workstation in the event of failure of the control computer. (Stakeholder Requirement)
- Status: Approved
- Artifact Format: Text

##### 4307: The AMR system functions, reports, and data on the control computer shall be securely accessible by properly authorized persons from other workstations on the City’s network. (Stakeholder Requirement)
- Artifact Format: Text
- Status: Approved
